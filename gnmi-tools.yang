module gnmi-tools {

  namespace "http://cisco.com/ns/yang/gnmi-tools";
  prefix gnmi-tools;

  description
    "This module contains a YANG data model for gnmi tools testing and
    development.";

  grouping combo {
    leaf empty-leaf { type empty; }
    container down {
      leaf str-leaf {type string; }
      leaf int-leaf {type int32; }
    }
    container pres {
      presence true;
    }
  }

  grouping top-list {
    list top-list {
      key name;
      leaf name {type string;}
      uses combo;
    }
  }

  container gnmi-tools {
    container top {
      uses combo;
    }

    container top-pres {
      presence true;
      uses combo;
    }

    uses top-list;

    list double-key-list {
        key "name type";
        leaf name {type string;}
        leaf type {type string;}
        leaf admin-state {type string;}
    }

    container top-for-delete {
      uses top-list;
    }
  }

}
